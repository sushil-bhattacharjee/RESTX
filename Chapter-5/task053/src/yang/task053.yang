module task053 {

  namespace "http://example.com/task053";
  prefix task053;

  import ietf-inet-types {
    prefix inet;
  }
  import tailf-common {
    prefix tailf;
  }
  import tailf-ncs {
    prefix ncs;
  }

  description
    "Bla bla...";

  revision 2025-02-20 {
    description
      "Creating vrf for task053";
  }

  list task053 {
    description "This is an RFS skeleton service";

    key name;
    leaf name {
      tailf:info "Unique service id";
      tailf:cli-allow-range;
      type string;
    }

    uses ncs:service-data;
    ncs:servicepoint task053-servicepoint;

    // may replace this with other ways of refering to the devices.
    leaf-list device {
      type leafref {
        path "/ncs:devices/ncs:device/ncs:name";
      }
    }

    // replace with your own stuff here
    leaf vrfnumber {
      type int8;
    }
    leaf-list interfaces {
      tailf:info "Ethernet interfaces";
      description  "List of interfaces exa GigabitEthernet 0/0";
      type string;
    }
  }
}
